BMS DEFINITIONS AUTOMATIC TAGS ::= BEGIN

-- Convert to voltage with ((float)val * 3.3) / (1 &lt;&lt; 12)
BMSADCValue ::= INTEGER(0..65535)

-- Signed millidegrees Celsius; -2147483648 means invalid or not yet sampled.
BMSTemperatureMilliCelsius ::= INTEGER(-2147483648..2147483647)
bmsTemperatureInvalid INTEGER ::= -2147483648

-- Status of an individual cell
BMSCellStatus ::= SEQUENCE {
    -- Cell Over Voltage
    overvoltage BOOLEAN,
    -- Cell Under Voltage
    undervoltage BOOLEAN,
    -- Direct Reading Voltage
    voltage BMSADCValue
}

-- Status of a battery pack
BMSBatteryPackStatus ::= SEQUENCE {
    -- Status of cell A
    cellA BMSCellStatus,
    -- Status of cell B
    cellB BMSCellStatus,
    -- Direct Reading of Current Sensor VUR
    currentDraw BMSADCValue,
    -- Direct Reading of Current Current Sensor CHR
    currentCharge BMSADCValue,
    -- Direct Reading of Combined Voltage
    voltage BMSADCValue,
    -- Battery Over Current flag
    overcurrent BOOLEAN
}


lfpIdBMSPowerStatusRequest INTEGER ::= 2
BMSPowerStatusRequest ::= SEQUENCE {
    placeholder INTEGER(0) -- Empty struct placeholder
}

lfpIdBMSPowerStatusResponse INTEGER ::= 3
BMSPowerStatusResponse ::= SEQUENCE {
    -- Status of battery pack 1
    batteryPack1 BMSBatteryPackStatus,
    -- Status of battery pack 2
    batteryPack2 BMSBatteryPackStatus
}



-- Override Heater output (BMS Self control heaters)
lfpIdBMSSetHeaterDutyRequest INTEGER ::= 4
BMSSetHeaterDutyRequest ::= SEQUENCE {
    -- Duty Cycle of PWM Wave for Heater 1
    heater1 INTEGER(0..99) OPTIONAL,
    -- Duty Cycle of PWM Wave for Heater 2
    heater2 INTEGER(0..99) OPTIONAL,
    -- Duty Cycle of PWM Wave for Heater 3
    heater3 INTEGER(0..99) OPTIONAL,
    -- Duty Cycle of PWM Wave for Heater 4
    heater4 INTEGER(0..99) OPTIONAL
}

lfpIdBMSSetHeaterDutyResponse INTEGER ::= 5
BMSSetHeaterDutyResponse ::= SEQUENCE {
    responseCode INTEGER(0..1) -- 0 = success (command applied), 1 = failure
}




lfpIdBMSTemperatureStatusRequest INTEGER ::= 6
BMSTemperatureStatusRequest ::= SEQUENCE {
    placeholder INTEGER(0) -- Empty struct placeholder
}

lfpIdBMSTemperatureStatusResponse INTEGER ::= 7
BMSTemperatureStatusResponse ::= SEQUENCE {
    -- Converted thermistor temperatures in signed millidegrees Celsius.
    -- Invalid channels contain bmsTemperatureInvalid; raw ADC counts are not sent.
    thermistors SEQUENCE SIZE(8) OF BMSTemperatureMilliCelsius
}



END
