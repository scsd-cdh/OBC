SYSTEMS DEFINITIONS AUTOMATIC TAGS ::= BEGIN

groundSystemId INTEGER ::= 0
cdhSystemId INTEGER ::= 1
bmsSystemId INTEGER ::= 2
pdsSystemId INTEGER ::= 3
commsSystemId INTEGER ::= 4

-- endpoints


END
